# req

## #1: Specifications (Container)
System Specifications

### #3: Operate from 100-300VDC (Functional)

### #4: Soft shutdown current path to pump (Functional)

### #5: Switch between AC & DC Inputs (Functional)

### #6: Disable and Enable output baised on pressure, flow, power (Functional)

### #7: Provide remote interface to system and send data to web server (Functional)

### #11: Operate a pump (Functional)

### #13: Turn pump on and off (Functional)

### #14: AC Switchover button (Functional)

## #2: System Requirements (Functional)

### #12 (Functional)
